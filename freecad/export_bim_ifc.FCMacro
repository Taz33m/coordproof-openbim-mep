"""Best-effort FreeCAD BIM/IFC review export helper.

Run after organizing the model with FreeCAD BIM. This macro exports all visible
document objects to `bim/mechanical_room_freecad_review.ifc` where possible.
The authoritative OpenBIM deliverable is generated by `tools/generate_ifc.py`.
"""

import os
import sys

import FreeCAD as App


ROOT = os.path.abspath(os.path.join(os.path.dirname(__file__), ".."))
IFC_PATH = os.environ.get(
    "COORDPROOF_FREECAD_REVIEW_IFC_PATH",
    os.path.join(ROOT, "bim", "mechanical_room_freecad_review.ifc"),
)
BIM_PATH = os.environ.get(
    "COORDPROOF_FREECAD_BIM_PATH",
    os.path.join(ROOT, "freecad", "mechanical_room_bim.FCStd"),
)

doc = App.ActiveDocument or App.openDocument(BIM_PATH)
if doc is None:
    raise RuntimeError("Open or build the mechanical room document before exporting IFC.")

objects = [obj for obj in doc.Objects if hasattr(obj, "Shape")]
if not objects:
    raise RuntimeError("No shape-bearing objects found for IFC export.")

try:
    bim_importers = os.path.join(
        os.path.dirname(os.path.dirname(App.getResourceDir())), "Mod", "BIM", "importers"
    )
    if bim_importers not in sys.path:
        sys.path.append(bim_importers)
    import exportIFC

    colors = {}
    for obj in objects:
        view = getattr(obj, "ViewObject", None)
        if view and hasattr(view, "ShapeColor"):
            colors[obj.Name] = view.ShapeColor
    project = None
    for obj in doc.Objects:
        if (
            getattr(obj, "IfcType", None) == "Project"
            and getattr(obj, "Label", "") == "Project_CoordProof_MechanicalRoom"
        ):
            project = obj
            break
    parts = [obj for obj in doc.Objects if obj.TypeId == "Part::Feature"]
    if project is not None and hasattr(project, "IfcType"):
        export_objects = [project] + parts
    else:
        export_objects = parts
    exportIFC.export(export_objects, IFC_PATH, colors=colors)
    print("Exported IFC with FreeCAD BIM exporter:", IFC_PATH)
except Exception as exc:
    raise RuntimeError(
        f"IFC export failed. Confirm FreeCAD BIM/IFC support is installed and retry. Cause: {exc}"
    ) from exc
